-- ##############################################################################################
--  ASN.1 structured proprietary extensions
-- ##############################################################################################
--     !!! This file is not versioned !!!
--     Changes in an extension definition must be made using a new extension id. 
--     The new definition will then be added to this file  
-- 
-- ##############################################################################################

-- ##############################################################################################
--  VDV extension to be used to transport proprietary VDV codes.
-- ##############################################################################################
--  extensionId = "*VDV1"
-- ##############################################################################################
VDV1Extension ::= SEQUENCE {
    -- issuer code using the default code table of the product owner (today used e.g. by VDV)
    externalIssuerId        INTEGER      OPTIONAL,
    -- authorization id provided to the issuer by the poroduct owner (today used e.g. by VDV)
    issuerAuthorizationId            INTEGER      OPTIONAL,
    ... -- /!\ TODO Manuel
}
