ASN-Module-Header { iso(1) identified-organization(3) dod(6)
    internet(1) private(4) enterprise(1) uic(17218) fcb(1) modules(0) header(1) v3(3) 0 }
    DEFINITIONS AUTOMATIC TAGS ::= BEGIN

-- imports and exports
-- EXPORTS ALL;

IMPORTS CompanyCode, Data, Timestamp
 FROM ASN-Module-GeneralData { iso(1) identified-organization(3) dod(6) internet(1) private(4) enterprise(1) uic(17218) fcb(1) modules(0) general(5) v1(1) 0 };

-- ##############################################################################################
-- # UIC barcode header - version 3.0.0
-- #
-- # Naming and encoding conventions
-- #   - A bar code which is only static (printed on a paper), and for which the security is in the system,
-- #      does not need any of these elements.
-- #   - A bar code which is only static, and includes its own security, needs:
-- #  	  level1Signature
-- #      level1KeyAlg and level1SigningAlg if the associated key does not make this evident
-- #   - A dynamic bar code including static and dynamic signatures needs the same elements as a static bar code, plus:
-- #	  level2PublicKey, and level2Signature
-- #      level2SigningAlg and level2keyAlg if not evident
-- #
-- # The maximum size of a barcode is, per the Aztec specification ISO 24778, limited to 1914 bytes.
-- ##############################################################################################

-- The basic entry point of the barcode
UICBarcodeHeader ::= SEQUENCE {
    -- This field SHALL be set to the byte string "U3".
    -- This results in the version 3 header being prefixed with U3 at the start, allowing identification of this
    --  format of barcode header.
    format      OCTET STRING (SIZE(2)),
    contents    StandardSignedData{Level2Data, NULL}
}

Level2Data ::= SEQUENCE {
    level1Data  Level1Data,
    -- Dynamic Content Data goes here
    data  SEQUENCE SIZE(1..8) OF Data OPTIONAL
}

-- Provider of the level 1 signature
CompanyKeyReference ::= SEQUENCE {
    securityProvider    CompanyCode,
    keyId               INTEGER (0..99999)
}

Level1Data ::= CHOICE {
    -- Must use the standard variety, message recovery format to be decided upon at a later date
    -- Standard variety signature calculated over BarcodeTBSData
    directlyIssued  SignedData{BarcodeData, CompanyKeyReference},
    -- Must not be used, format to be decided upon at a later date
    subIssued       SEQUENCE {
        -- Standard variety signature calculated over EndEntityCertificateTBSData
        endEntityCertificate    SignedData{EndEntityCertificate, CompanyKeyReference},
        barcodeData             SignedData{BarcodeData, NULL}
    }
}

BarcodeTBSData ::= StandardTBSData{BarcodeData, CompanyKeyReference}
EndEntityCertificateTBSData ::= StandardTBSData{EndEntityCertificate, CompanyKeyReference}

SignedData{DataType, KeyReference} ::= CHOICE {
    standard        StandardSignedData{DataType, KeyReference},
    messageRecovery MessageRecoverySignature
}

StandardSignedData{DataType, KeyReference} ::= SEQUENCE {
    tbs         DataType,
    -- The signature is calculated over the canonical unaligned PER (CUPER) encoding of StandardTBSData{DataType, KeyReference}
    -- Note: when KeyReference is NULL this is equivalent to the CUPER encoding of DataType
    signature   SEQUENCE {
        keyReference    KeyReference,
        data            Signature
    } OPTIONAL -- Being unset only permitted when no security is required
}

StandardTBSData{DataType, KeyReference} ::= SEQUENCE {
    keyReference    KeyReference,
    tbs             DataType
}

-- Values taken from the JSON Web Signature and Encryption Algorithm registry
-- https://www.iana.org/assignments/jose/jose.xhtml#web-signature-encryption-algorithms
Signature ::= CHOICE {
    es256       DSSSignature{32}, -- ECDSA using P-256 and SHA-256
    es256k      DSSSignature{32}, -- ECDSA using secp256k1 curve and SHA-256
    es384       DSSSignature{48}, -- ECDSA using P-384 and SHA-384
    es512       DSSSignature{66}, -- ECDSA using P-521 and SHA-512
    ed25519     OCTET STRING (SIZE (64)),
    ed448       OCTET STRING (SIZE (114)),
    hs256       OCTET STRING (SIZE (32)), -- HMAC using SHA-256, not permitted except by bilateral agreement
    hs384       OCTET STRING (SIZE (48)), -- HMAC using SHA-384, not permitted except by bilateral agreement
    hs512       OCTET STRING (SIZE (64)), -- HMAC using SHA-512, not permitted except by bilateral agreement
    dsa1        DSSSignature{20}, -- DSA-1024 using SHA-1, not recommended for new deployments
    dsa224      DSSSignature{32}, -- DSA-2048 using SHA-224, not recommended for new deployments
    dsa256      DSSSignature{32}, -- DSA-2048 using SHA-256, not recommended for new deployments
    reserved1   NULL, -- Space for future signature modes, e.g. Post-Quantum Cryptography
    reserved2   NULL,
    reserved3   NULL,
    other       SEQUENCE {
        algId       OBJECT IDENTIFIER,
        signature   OCTET STRING
    }
}

DSSSignature{INTEGER: len} ::= SEQUENCE {
    r OCTET STRING (SIZE(len)),
    s OCTET STRING (SIZE(len))
}

PublicKey ::= CHOICE {
    nistP256    ECPublicKey{32},
    secp256K1   ECPublicKey{32},
    nistP384    ECPublicKey{48},
    nistP521    ECPublicKey{66},
    ed25519     OCTET STRING (SIZE (32)),
    ed448       OCTET STRING (SIZE (57)),
    reserved    NULL, -- Space for future public key formats, e.g. Post-Quantum Cryptography
    other       OCTET STRING -- DER encoded SubjectPublicKeyInfo
}

ECPublicKey{INTEGER: len} ::= SEQUENCE {
    x OCTET STRING (SIZE(len)),
    yIsOdd BOOLEAN
}

-- Purposefully left blank, format to be decided upon at a later date
MessageRecoverySignature ::= NULL
-- Purposefully left blank, format to be decided upon at a later date
EndEntityCertificate ::= NULL

BarcodeData ::= SEQUENCE {
    -- This field MUST contain at most one well-known UIC data type (e.g. FCBn)
    data                SEQUENCE SIZE(1..16) OF Data,

    level2PublicKey     PublicKey                       OPTIONAL,

    -- End of the validity of the barcode.
    -- After this date and time the bar code needs to be regenerated by the provider of the ticket.
    -- The provider of the bar code should ensure that the endOfValidity given here does not exceed the validity of the key pair used on level 2.
    endOfValidity       Timestamp                       OPTIONAL,

    -- Validity duration in seconds of the barcode with reference to the time stamp in the dynamic content data
   	validityDuration    INTEGER (1..3600)               OPTIONAL,

   	...
}

END
